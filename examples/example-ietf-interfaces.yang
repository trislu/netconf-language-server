module example-ietf-interfaces {
  yang-version 1.1;
  namespace "urn:example:interfaces";
  prefix if;

  organization "Example";
  description "Minimal stand-in for ietf-interfaces to demo cross-file goto.";

  revision 2026-01-01;

  typedef interface-ref {
    type leafref {
      path "/if:interfaces/if:interface/if:name";
    }
  }

  container interfaces {
    list interface {
      key "name";
      leaf name { type string; }
      leaf enabled { type boolean; default true; }
      leaf description { type string; }
    }
  }
}
