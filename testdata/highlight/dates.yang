module dates {
  yang-version 1.1;
  namespace "urn:dates";
  prefix dt;

  // Revision dates (known gap, in baseline).
  revision 2020-05-29 { description "third"; }
  revision 2018-04-23 { description "second"; }
  revision 2017-05-08 { description "first"; }
}
